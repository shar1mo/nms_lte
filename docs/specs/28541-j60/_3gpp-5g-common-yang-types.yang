module _3gpp-5g-common-yang-types {
  yang-version 1.1;
  namespace "urn:3gpp:sa5:_3gpp-5g-common-yang-types";
  prefix "types5g3gpp";

  import ietf-yang-types { prefix yang; }
  import ietf-inet-types { prefix inet; }
  import _3gpp-common-yang-types { prefix types3gpp; }

  organization "3GPP SA5";
  contact "https://www.3gpp.org/DynaReport/TSG-WG--S5--officials.htm?Itemid=464";
  description "The model defines common types for 5G networks and
    network slicing.
    Copyright 2025, 3GPP Organizational Partners (ARIB, ATIS, CCSA, ETSI, TSDSI,
    TTA, TTC). All rights reserved.";
  reference "3GPP TS 28.541";

  revision 2025-11-07 { reference CR-1640 ; }
  revision 2025-11-01 { reference CR-1657 ; }
  revision 2025-07-25 { reference CR-1558 ; }
  revision 2025-03-25 { reference CR-1489 ; }
  revision 2024-11-01 { reference CR-1405; }
  revision 2024-10-06 { reference CR-1389; }
  revision 2024-05-24 { reference CR-1273 ; }
  revision 2023-09-18 { reference CR-1043 ; }
  revision 2023-05-10 { reference CR-0916; }
  revision 2021-08-05 { reference S5-214053/CR-0518; }
  revision 2020-11-05 { reference CR-0412 ; }
  revision 2019-10-20 { reference "Initial version."; }

  grouping AreaScopeGrp {
    description "This <<dataType>> defines an area scope.";

    choice AreaScopeChoice {

      case eutran-only { // choice 1
        leaf-list eutraCellIdList {
          type types3gpp:EutraCellId;
          min-elements 1;
          max-elements 32;
          description "List of E-UTRAN cells identified by E-UTRAN-CGI";
        }
      }
      case tac { // choice 3
        leaf-list tacList { 
          type types3gpp:Tac;
          min-elements 1;
          max-elements 8;
          description "Tracking Area Code list";
        }
        leaf-list cAGIdList { 
          type types3gpp:CagId;
          max-elements 256;
          description "It identifies a CAG list containing up to 
            256 CAG-identifiers per UE or up to 12 CAG-identifiers 
            per cell, see TS 38.331 [38]. CAG ID is used to combine 
            with PLMN ID to identify a PNI-NPN.AG ID is a hexadecimal 
            range with size 32 bit.";
        }
      }

      case ntnGeoAreaList{ // choice 6
        list ntnGeoAreaList {
          must 'not(../nrCellIdList)';
          description "geographical areas for NTN MDT";
          key idx;
          max-elements 8;
          leaf idx { type string; }
          uses types3gpp:GeoAreaGrp;
        }
      }

      case else {
        list nPNIdentityList { // choice 2, 4 , 5
          description "list of NPN IDs of in NR. It is either 
            a list of PNI-NPNs identified by CAG ID with 
            associated plmn-Identity or a list of SNPN 
            identified by Network ID with associated plmn-Identity";
          key idx;
          min-elements 1;
            uses types3gpp:NpnIdGrp;
          leaf idx { type string; }
        }
        leaf-list nrCellIdList {
          must 'not(../taiList)';
          type types3gpp:NrCellId;
          max-elements 32;
          description "List of NR cells identified by NG-RAN CGI";        
        }
        list taiList {
          must 'not(../nrCellIdList)';
          description "Tracking Area Identity list";
          key idx;
          max-elements 8;
          leaf idx { type string; }
          uses types3gpp:TaiGrp;
        }

      }
    }
        

    list sliceIdList {
      description "Network Slice Id list";
      key idx;
      uses PLMNInfo;
      min-elements 1;
      max-elements 16384;
      leaf idx { type string; }
    }
  }

  grouping IpInterfaceGrp {
    leaf-list ipv4EndpointAddresses {
      description "Available endpoint IPv4 address(es) of
        the User Plane interface.";
      type inet:ipv4-address;
      must '../ipv4EndpointAddresses or ../ipv6EndpointAddresses or ../fqdn';
    }

    leaf-list ipv6EndpointAddresses {
      description "Available endpoint IPv6 address(es) of
        the User Plane interface.";
      type inet:ipv6-address;
      must '../ipv4EndpointAddresses or ../ipv6EndpointAddresses or ../fqdn';
      }

    leaf fqdn {
      description "This parameter defines FQDN of the Network Function
        (See TS 23.003).";
      type inet:domain-name;
      must '../ipv4EndpointAddresses or ../ipv6EndpointAddresses or ../fqdn';
      }
  }

  grouping SdRangeGrp {
    leaf start {
      type string {
         pattern "[A-Fa-f0-9]{6}";
       }
      mandatory true;
      description "First value identifying the start of an SD range.
        This string shall be formatted as specified for the sd attribute of the
        Snssai data type in clause 5.4.4.2 of TS 29.571.";
    }

    leaf end {
      type string {
         pattern "[A-Fa-f0-9]{6}";
       }
      mandatory true;
      description "Last value identifying the end of an SD range.
      This string shall be formatted as specified for the sd attribute of the
        Snssai data type in clause 5.4.4.2 in TS 29.571";
    }
  }

  grouping SnssaiExtensionGrp {
    list sdRanges {
      min-elements 1;
      key "start end";
      description "It shall contain the range(s) of Slice Differentiator values
        supported for the Slice/Service Type value indicated in the sst
        attribute of the Snssai data type (see clause 5.4.4.2 in TS 29.571).";
      uses SdRangeGrp;
    }

    leaf wildcardSd {
      type boolean;
      default false;
      description "It indicates that all SD values are supported for the
        Slice/Service Type value indicated in the sst attribute of the Snssai
        data type (see clause 5.4.4.2 in TS 29.571).";
    }
  }

  grouping ExtSnssaiGrp {
    list snssai {
      description "It represents the S-NSSAI the NetworkSlice managed object
        is supporting. The S-NSSAI is defined in TS 23.003 ";
      min-elements 1;
      max-elements 1;
      key "sd sst";
      uses SNssai;
    }

    list snssaiExtension {
      description "It represents extensions to the Snssai.";
      min-elements 1;
      key idx;
      leaf idx { type uint32; }
      uses SnssaiExtensionGrp;
    }
  }
    grouping sNssaiSmfInfoItem {
    list sNssai {
      description "Supported S-NSSAI.";
      min-elements 1;
      max-elements 1;
      key "sst sd";
      uses SNssai;
    }

    list dnnSmfInfoList {
      description "List of parameters supported by the SMF per DNN.
      The absence indicates the DNN can be selected for any DNAI.";
      min-elements 1;
      key dnn;
      uses DnnSmfInfoItem;
    }
  }

  grouping MappedCellIdInfoGrp {
    description "This data type represents the mapping relationship between
      Mapped Cell IDs and geographical areas (see clause 16.14.5 of TS 38.300";

    list ntnGeoArea {
      description "This attribute indicates a specific geographical location
        mapped to Mapped Cell ID(s).";
      min-elements 1;
      max-elements 1;
      key idx;
      leaf idx { type uint32; }
      uses types3gpp:GeoAreaGrp;
    }

    list mappedCellId  {
      description "This attribute is in format of NCGI to indicate a fixed
        geographical area (See subclause 16.14.5 in TS 38.300)";
      min-elements 1;
      max-elements 1;
      key idx;
      leaf idx { type uint32; }
      uses NcgiGrp;
    }
  }

  grouping NcgiGrp {
    description "Represents the Ncgi datatype";

    list plmnId {
      description "This attribute represents a PLMN Identity.";
      min-elements 1;
      max-elements 1;
      key "idx";
      leaf idx { type uint32 ; }
      uses types3gpp:PLMNId ;
    }

    leaf nrCellId {
      type string;
      mandatory true;
      description "This attribute represents NR Cell Identity.
        It's a 36-bit string identifying an NR Cell Id as specified in
        clause 9.3.1.7 of TS 38.413, in hexadecimal representation. Each
        character in the string shall take a value of
        '0' to '9', 'a' to 'f' or 'A' to 'F' and shall represent 4 bits.
        The most significant character representing the 4 most significant
        bits of the Cell Id shall appear first in the string, and the
        character representing the 4 least significant bit of the
        Cell Id shall appear last in the string.

        Pattern: '^[A-Fa-f0-9]{9}$'

        Example:
        An NR Cell Id 0x225BD6007 shall be encoded as '225BD6007'.";
    }

    leaf nId {
      type string;
      mandatory true;
      description "Network Identity; Shall be present if PlmnIdNid identifies
        an SNPN (see clauses 5.30.2.3, 5.30.2.9, 6.3.4, and 6.3.8 in
        3GPP TS 23.501.";
    }
  }

  typedef NRTAC {
    type string;
    description "This holds the identity of the common Tracking Area Code
      for the PLMNs.

      allowedValues:
      a) It is the TAC or Extended-TAC.
      b) A cell can only broadcast one TAC or Extended-TAC. See TS 36.300,
        subclause 10.1.7 (PLMNID and TAC relation).
      c) TAC is defined in subclause 19.4.2.3 of 3GPP TS 23.003
       and Extended-TAC is defined in subclause 9.3.1.29 of 3GPP TS 38.473.
      d) For a 5G SA (Stand Alone), it has a non-null value.";
  }

  grouping SNssai {
    description
      "Single Network Slice Selection Assistance Information(S-NSSAI)";
    reference "3GPP TS 23.003";

    leaf sd {
      description "Slice Differentiator
        If not needed, the value can be set to ff:ff:ff.";
      type yang:hex-string {
        length 8;
      }
      reference "3GPP TS 23.003";
    }

    leaf sst {
      type uint8;
      description "Slice/Service Type.
         Values 0 to 127 belong to standardized SST range and are defined in
         3GPP TS 23.501. Values 128 to 255 belong to operator-specific range.";
    }
  }

  grouping PlmnIdNid {
    description "Represents the SCP domain specific information as defined
      in TS 29.510 ";
    uses types3gpp:PLMNId;

    leaf nid {
      type string;
      description "This attribute represents network Identity;
        Shall be present if PlmnIdNid identifies an SNPN.
        (see clauses 5.30.2.3, 5.30.2.9, 6.3.4, and 6.3.8 in TS 23.501";
    }
  }

  grouping PLMNInfo {
    description "The PLMNInfo data type define a S-NSSAI member in a specific
      PLMNId, and it have two attributes PLMNId and S-NSSAI (PLMNId, S-NSSAI).
      The PLMNId represents a data type that is comprised of mcc
      (mobile country code) and mnc (mobile network code), (See TS 23.003
      subclause 2.2 and 12.1) and S-NSSAI represents an data type, that is
      comprised of an SST (Slice/Service type) and an optional
      SD (Slice Differentiator) field";
    uses types3gpp:PLMNId;
    uses SNssai;
  }

  typedef CommModelType {
    reference "3GPP TS 23501";
    type enumeration {
      enum DIRECT_COMMUNICATION_WO_NRF {
        value 0;
        description "Directly communicate to other pre-configured NF service.";
      }

      enum DIRECT_COMMUNICATION_WITH_NRF {
        value 1;
        description "Directly communicate to other NF service discovered
          by NRF.";
      }

      enum INDIRECT_COMMUNICATION_WO_DEDICATED_DISCOVERY {
        value 2;
        description "Communicate to pre-configured other NF service through
          SCP as a proxy.";
      }

      enum INDIRECT_COMMUNICATION_WITH_DEDICATED_DISCOVERY {
        value 3;
        description "Communication to NF service discovered by NRF through SCP
          as a proxy.";
      }

    }
  }

  grouping CommModel {
    leaf groupId {
      type uint16;
    }
    leaf commModelType {
      type CommModelType;
    }
    leaf-list targetNFServiceList {
      type types3gpp:DistinguishedName;
    }
    leaf commModelConfiguration {
      type string;
    }
  }
  grouping TaiRangeGrp {
    list plmnId {
      description "PLMN ID related to the TacRange.";
      min-elements 1;
      max-elements 1;
      key "mcc mnc";
      uses types3gpp:PLMNId;
    }

    list tacRangeList {
      description "The range of the TACs.";
      min-elements 1;
      key "start end";
      uses TacRange;
    }
  }

  grouping TacRange {
    leaf start {
      description "First value identifying the start of a TAC range,
      to be used when the range of TAC's can be represented
       as a hexadecimal range (e.g., TAC ranges).";
      type string {
        pattern '^([A-Fa-f0-9]{4}|[A-Fa-f0-9]{6}$)';
      }
    }

    leaf end {
      description "Last value identifying the end of a TAC range,
      to be used when the range of TAC's can be represented as
       a hexadecimal range (e.g. TAC ranges).";
      type string {
        pattern '^([A-Fa-f0-9]{4}|[A-Fa-f0-9]{6})$';
      }
    }

    leaf nRTACpattern {
      description "Pattern (regular expression according to the ECMA-262)
        representing the set of TAC's belonging to this range.
        A TAC value is considered part of the range if and only if the
        TAC string fully matches the regular expression.";
      type string;
    }
  }
    grouping DnnSmfInfoItem {
    leaf dnn {
      description "Supported DNN.";
      mandatory true;
      type string;
    }

    leaf-list dnaiList {
      description "List of Data network access identifiers supported by
      the SMF for this DNN. The absence of this attribute indicates that
       the SMF can be selected for this DNN for any DNAI.";
      min-elements 1;
      type string;
    }
  }

  grouping SupportedFunc {
    leaf function {
      type string;
    }
    leaf policy {
      type string;
    }
  }

  typedef EnergySavingLoadThresholdT {
    type uint32 {
      range 0..10000;
    }
    units 1/10000;
  }

  typedef EnergySavingTimeDurationT {
    type uint32 {
      range 0..900;
    }
    units seconds;
  }

  typedef PhysCellID {
    type uint32 {
      range "0..1007";
    }
    reference "clause 7.4.2 of TS 38.211";
  }

  typedef UTC24TimeOfDayT {
    description "Time of day in HH:MM or H:MM 24-hour format per UTC
      time zone.";
    type string {
      pattern "(([01]?[0-9])|(2[0-3])):([0-5][0-9])";
    }
  }

  typedef DayOfWeekT {
    type enumeration {
      enum Monday;
      enum Tuesday;
      enum Wednesday;
      enum Thursday;
      enum Friday;
      enum Saturday;
      enum Sunday;
    }
  }

  grouping CaraConfigurationGrp {
    description "This data type represents the configuration used for 
    an NR mobile node (e.g., IAB-node or MWAB), to perform certificate enrolment procedure with
    Certification Authority server (CA/RA) as specified in TS 28.315 clause 5.3";
    
    leaf caraAddress {
      type inet:host;
      description "IP address or FQDN of the CMP (Certificate Management Protocol) server";
    }

    leaf portNumber {
        type inet:port-number;     
        description "This parameter specifies the port number used by 
        CMP (Certificate Management Protocol) server. The port for HTTP/HTTPSs 
        transfer of CMP messages is not explicitly given in RFC 9811, therefore
        this parameter is required. The port number is usually 
        represented as 2 octets.";
    }
    
    leaf path {
        type inet:uri;
        mandatory true;        
        description "This parameter specifies the path (in ASCII string) to 
          the CMP server directory. A CMP server may be located in an 
          arbitrary path other than root.";
    }

    leaf subjectName {
        type string;
        mandatory true;        
        description "This parameter specifies the subject name (in ASCII 
          string) of the CA/RA. The use is described in 3GPP TS 33.310
          clause 9.5.3.";
    }

    leaf protocol {
        type enumeration {
          enum HTTP;
          enum HTTPS;
        }
        description "This parameter specifies the protocol (HTTP or HTTPS) 
          to be used for certificate enrolment. The use is described in 
          3GPP TS 33.310 clause 9.6.";
    }
  }
  
  grouping MnrOamIPConfigGrp { 
    description "This data type includes the configutation for OAM connectivity  
      used for  an NR mobile node (e.g., IAB-node or MWAB), to establish connection with
      management system. The configuration attributes include: 
      Configuration of certification authority (CA/RA) server, 
      Configuration of security gateway (SeGW), and 
      Configuration of software configuration server (SCS)";
    
    list caraConfiguration {
      description "configuration used for  an NR mobile node (e.g., IAB-node or MWAB),
        to perform certificate enrolment procedure as specified in 
        TS 28.315.";
      uses CaraConfigurationGrp;
      max-elements 1;
      key caraAddress; 
    }

    leaf seGwConfiguration {
      description "this parameter specifies IP address or
        FQDN of security gateway (SeGW) used for an 
         an NR mobile node (e.g., IAB-node or MWAB)
        to establish secure connection as specified in TS 28.315.";
      type inet:host;

    }

    leaf scsConfiguration {
      description "this parameter specifies IP address or FQDN of 
        configuration server (SCS) used for 
        an NR mobile node (e.g., IAB-node or MWAB)
        to establish connection as specified in TS 28.315.";        
      type inet:host; 
    }
  }

  grouping LocationInfoGrp {
    description "This data type contains location information 
      of an NR mobile node (e.g., IAB-node or MWAB).";
    
    leaf gNBId {
      type int64 { range "0..4294967295"; }
      description "It is either the gNB ID of the IAB-donor-CU that target IAB-DU
      connects to or the gNB Id of the IAB-nonor-CU that serves IAB-MT, or
      the gNBId of the gNB that serves MWAB-UE.";
    }

    list pLMNId {
      uses types3gpp:PLMNId;
      max-elements 1;
      description "The PLMN ID where IAB-MT or MWAB-UE is connected to";
      key "mcc mnc";
    }

    leaf cellLocalId {
      type int32 { range "0..16383"; }
      description "Identifies an NR cell where IAB-MT or MWAB-UE 
      is connected to.";
    }

    leaf nRTAC {
      type types5g3gpp:NRTAC;
      description "It is TAC pertaining to the cells where IAB-MT or MWAB-UE is 
        connected.";
    }

    list tAI {
      uses types3gpp:TaiGrp;
      key idx;
      leaf idx { type string; }
      max-elements 1; 
      description "It is the TAI (see subclause 9.3.3.11 in TS 38.413) pertaining
        to the cells where IAB-MT or MWAB-UE is connected";
    }
    list geoArea {
      uses types3gpp:GeoAreaGrp;
      key idx;
      leaf idx {type string;}
      max-elements 1;       
      description "It specifies geographical area of mobile NR node
      (e.g., IAB-node or MWAB-node).";
    }
  }
}
