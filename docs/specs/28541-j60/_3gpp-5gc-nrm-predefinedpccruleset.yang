module _3gpp-5gc-nrm-predefinedpccruleset {
  yang-version 1.1;

  namespace urn:3gpp:sa5:_3gpp-5gc-nrm-predefinedpccruleset;
  prefix PredPccRules3gpp;

  import _3gpp-common-managed-element { prefix me3gpp; }
  import _3gpp-common-top { prefix top3gpp; }
  import _3gpp-5gc-nrm-smffunction { prefix smf3gpp; }
  import _3gpp-5gc-nrm-pcffunction { prefix pcf3gpp; }
  import ietf-yang-types { prefix yang; }

  organization "3gpp SA5";
  contact "https://www.3gpp.org/DynaReport/TSG-WG--S5--officials.htm?Itemid=464";
  description "This IOC represents the predefined PCC rules, which are
    configured to SMF and referenced by PCF.
    Copyright 2025, 3GPP Organizational Partners (ARIB, ATIS, CCSA, ETSI, TSDSI,
    TTA, TTC). All rights reserved.";
  reference "3GPP TS 28.541";

  revision 2025-05-01 { reference CR-xxxx ; }
  revision 2025-04-25 { reference CR-1520 ; }
  revision 2025-03-25 { reference CR-1489 ; }
  revision 2023-09-18 { reference CR-1043 ; }
  revision 2023-04-26 { reference CR-0916; }
  revision 2020-10-04 { reference "CR-0393"; }
  revision 2020-08-21 { reference "CR-0330"; }

  grouping TscaiInputContainer {
    description "It specifies the transports TSCAI input parameters for TSC
      traffic at the ingress interface of the DS-TT/UE for a PCC rule.";
    reference " 3GPP TS 29.512";
    leaf periodicity {
      type uint32;
      description "It identifies the time period between the start of two bursts
        in reference to the TSN GM.";
      reference "3GPP TS 29.571.";
    }
    leaf burstArrivalTime {
      type yang:date-and-time;
      description "It Indicates the arrival time (in date-time format) of the
        data burst in reference to the TSN GM.";
      reference "3GPP,TS 29.571.";
    }
  }

  grouping ConditionData {
    description "It specifies the specifies the condition data for a PCC rule.";
    leaf condId {
      type string;
      mandatory true;
      description "It uniquely identifies the condition data.";
    }
    leaf activationTime {
      type yang:date-and-time;
      description " It indicates the time (in date-time format) when the decision
        data shall be activated.";
      reference "3GPP29.512 and TS 29.571.";
    }
    leaf deactivationTime {
      type yang:date-and-time;
      description "It indicates the time (in date-time format) when the decision
        data shall be deactivated.";
      reference "3GPPTS 29.512 and TS 29.571.";
    }
    leaf accessType {
      type enumeration {
        enum 3GPP_ACCESS;
        enum NON_3GPP_ACCESS;
      }
      description "It provides the condition of access type of the UE when the
        session AMBR shall be enforced.";
      reference "3GPPTS 29.512.";
    }
    leaf ratType {
      type enumeration {
        enum NR;
        enum EUTRA;
        enum WLAN;
        enum VIRTUAL;
        enum NBIOT;
        enum WIRELINE;
        enum WIRELINE_CABLE;
        enum WIRELINE_BBF;
        enum LTE-M;
        enum NR_U;
        enum EUTRA_U;
        enum TRUSTED_N3GA;
        enum TRUSTED_WLAN;
        enum UTRA;
        enum GERA;
      }
      description "It provides the condition of RAT type of the UE when the
        session AMBR shall be enforced.";
      reference "3GPPTS 29.512 and TS 29.571.";
    }
  }

  grouping SteeringMode {
    description "It specifies the traffic distribution rule, see TS 29.512.";
    leaf steerModeValue {
      type enumeration {
        enum ACTIVE_STANDBY;
        enum LOAD_BALANCING;
        enum SMALLEST_DELAY;
        enum PRIORITY_BASED;
      }
      mandatory true;
      description "It indicates the value of the steering mode, see TS 29.512.";
    }
    leaf active {
      type enumeration {
        enum 3GPP_ACCESS;
        enum NON_3GPP_ACCESS;
      }
      description "It indicates the active access, see TS 29.571.";
    }
    leaf standby {
      type enumeration {
        enum 3GPP_ACCESS;
        enum NON_3GPP_ACCESS;
      }
      description "It indicates the Standby access, see TS 29.571.";
    }
    leaf threeGLoad {
      type uint8 {
        range 0..100;
      }
      description "It indicates the traffic load to steer to the 3GPP Access
        expressed in one percent.";
    }
    leaf prioAcc {
      type enumeration {
        enum 3GPP_ACCESS;
        enum NON_3GPP_ACCESS;
      }
      description "It indicates the high priority access.";
        reference "3GPPTS 29.571";
    }
  }

  grouping UpPathChgEvent {
    description "It specifies the information about the AF subscriptions of the
      UP path change.";
    reference "3GPPTS 29.512";
    leaf notificationUri {
      type string;
      mandatory true;
      description "It provides notification address (Uri) of AF receiving the
        event notification.";
    }
    leaf notifCorreId {
      type string;
      mandatory true;
      description "It is used to set the value of Notification Correlation ID in
        the notification sent by the SMF, see TS 29.512";
    }
    leaf dnaiChgType {
      type enumeration {
        enum EARLY;
        enum EARLY_LATE;
        enum LATE;
      }
      mandatory true;
      description "It indicates the type of DNAI change, see TS 29.512";
    }
    leaf afAckInd {
      type boolean;
      default false;
      description "It identifies whether the AF acknowledgement of UP path
      event notification is expected.";
    }
  }

  grouping RouteInformation {
    description "It specifies the traffic routing information.";
    leaf ipv4Addr {
      type string;
      description "It defines the Ipv4 address of the tunnel end point in the
        data network, formatted in the dotted decimal notation.";
    }
    leaf ipv6Addr {
      type string;
      description "It defines the Ipv6 address of the tunnel end point in the
        data network.";
    }
    leaf portNumber {
      type uint32;
      mandatory true;
      description " It defines the UDP port number of the tunnel end point in
        the data network, see TS 29.571";
    }
  }

  grouping RouteToLocation {
    description "It specifies a list of location which the traffic shall be
      routed to for the AF request.";
    leaf dnai {
      type string;
      mandatory true;
      description "It represents the DNAI (Data network access identifier).";
      reference "3GPP 3GPP TS 23.501";
    }
    container routeInfo{
      description "It provides the traffic routing information.";
      uses RouteInformation;
    }
    leaf routeProfId {
      type string;
      description "It identifies the routing profile.";
    }
  }

  grouping RedirectInformaton {
    description "It specifies the redirect information for traffic control in
      the PCC rule.";
    leaf redirectEnabled {
      type boolean;
      mandatory true;
      description "It indicates whether the redirect instruction is enabled.";
    }
    leaf redirectAddressType {
      type enumeration {
        enum IPV4_ADDR;
        enum IPV6_ADDR;
        enum URL;
        enum SIP_URI;
      }
      mandatory true;
      description "It indicates the type of redirect address.";
      reference "3GPPTS 29.512";
    }
    leaf redirectServerAddress {
      type string;
      mandatory true;
      description "It indicates the address of the redirect server.";
    }
  }

  grouping TrafficControlDataInformation {
    description "It specifies the traffic control data for a service
      flow of a PCC rule.";
    leaf tcId {
      type string;
      mandatory true;
      description "It univocally identifies the traffic control policy data
        within a PDU session.";
    }
    leaf flowStatus {
      type enumeration {
        enum ENABLED-UPLINK;
        enum ENABLED-DOWNLINK;
        enum ENABLED;
        enum DISABLED;
        enum REMOVED;
      }
      mandatory true;
      description "It represents whether the service data flow(s) are enabled
        or disabled.";
    }
    container redirectInfo {
      description "It contains the redirect information indicating whether the
        detected application traffic should be redirected to another controlled
        address.";
      uses RedirectInformaton;
    }
    container addRedirectInfo {
      description "It contains the additional redirect information indicating
        whether the detected application traffic should be redirected to another
        controlled address.";
      list redirectInfo {
        description "The list of redirect information indicating whether the
          detected application traffic should be redirected to another
          controlled address.";
        key "redirectServerAddress";
        uses RedirectInformaton;
      }
    }
    leaf muteNotif {
      type boolean;
      default false;
      description "It indicates whether applicat'on's start or stop notification
        is to be muted.";
    }
    leaf trafficSteeringPolIdDl {
      type string;
      description "It references to a pre-configured traffic steering policy for downlink traffic at the SMF, see TS 29.512";
    }
    leaf trafficSteeringPolIdUl {
      type string;
      description "It references to a pre-configured traffic steering policy for
        uplink traffic at the SMF, see TS 29.512";
    }
    container routeToLocs {
      description "It provides a list of location which the traffic shall be
       routed to for the AF request.";
      list routeToLoc {
        description "The list of location which the traffic shall be routed to
          for the AF request.";
        key "dnai";
        uses RouteToLocation;
      }
    }
    uses UpPathChgEvent;
    leaf steerFun {
      type enumeration {
        enum MPTCP;
        enum ATSSS_LL;
      }
      description "It indicates the applicable traffic steering functionality.";
      reference "3GPPTS 29.512";
    }
    container steerModeDl {
      description "It provides the traffic distribution rule across 3GPP and
        Non-3GPP accesses to apply for downlink traffic.";
      uses SteeringMode;
    }
    container steerModeUl {
      description "It provides the traffic distribution rule across 3GPP and Non-3GPP accesses to apply for uplink traffic.";
      uses SteeringMode;
    }
    leaf mulAccCtrl {
      type enumeration {
        enum ALLOWED;
        enum NOT_ALLOWED;
      }
      description "It indicates whether the service data flow, corresponding to the service data flow template, is allowed or not allowed.";
    }
  }

  grouping ARP {
    description "It specifies the allocation and retention priority of a QoS control policy.";
    leaf priorityLevel {
      type uint8 {
        range 1..15;
      }
      mandatory true;
      description "It defines the relative importance of a resource request.";
    }
    leaf preemptCap {
      type enumeration {
        enum NOT_PREEMPT;
        enum MAY_PREEMPT;
      }
      mandatory true;
      description "It defines whether a service data flow may get resources that were already assigned to another service data flow with a lower priority level.";
    }
    leaf preemptVuln {
      type enumeration {
        enum NOT_PREEMPTABLE;
        enum PREEMPTABLE;
      }
      mandatory true;
      description "It defines whether a service data flow may lose the resources assigned to it in order to admit a service data flow with higher priority level.";
    }
  }

  grouping QosDataInformation {
    description "It specifies the QoS control policy data for a service flow of a PCC rule.";
    leaf qosId {
      type string;
      mandatory true;
      description "It identifies the QoS control policy data for a PCC rule.";
    }
    leaf fiveQIValue {
      type uint8 {
        range 0..255;
      }
      mandatory true;
      description "It indicates the 5QI value.";
    }
    leaf maxbrUl {
      type string;
      description "It represents the maximum uplink bandwidth.";
    }
    leaf maxbrDl {
      type string;
      description "It represents the maximum downlink bandwidth.";
    }
    leaf gbrUl {
      type string;
      description "It represents the guaranteed uplink bandwidth.";
    }
    leaf gbrDl {
      type string;
      description "It represents the guaranteed downlink bandwidth.";
    }
    uses ARP;
    leaf qosNotificationControl {
      type boolean;
      default false;
      description "It indicates whether notifications are requested from 3GPP NG-RAN when the GFBR can no longer (or again) be guaranteed for a QoS Flow during the lifetime of the QoS Flow.";
    }
    leaf reflectiveQos {
      type boolean;
      default false;
      description "Indicates whether the QoS information is reflective for the corresponding non-GBR service data flow";
    }
    leaf sharingKeyDl {
      type string;
      description "It indicates, by containing the same value, what PCC rules may share resource in downlink direction.";
    }
    leaf sharingKeyUl {
      type string;
      description "It indicates, by containing the same value, what PCC rules may share resource in uplink direction.";
    }
    leaf maxPacketLossRateDl {
      type uint16 {
        range 0..1000;
      }
      description "It indicates the downlink maximum rate for lost packets that can be tolerated for the service data flow.";
    }
    leaf maxPacketLossRateUl {
      type uint16 {
        range 0..1000;
      }
      description "It indicates the uplink maximum rate for lost packets that can be tolerated for the service data flow.";
    }
    leaf extMaxDataBurstVol {
      type uint32 {
        range 4096..2000000;
      }
      description "It denotes the largest amount of data that is required to be transferred within a period of 5G-AN PDB, see TS 29.512";
    }
  }

  grouping EthFlowDescription {
    description "It describes an Ethernet flow.";
    leaf destMacAddr {
      type string;
      mandatory true;
      description "It specifies the destination MAC address formatted in the
        hexadecimal .";
      reference "clause 1.1 and clause 2.1 of IETF RFC";
    }
    leaf ethType {
      type string;
      mandatory true;
      description "A two-octet string that represents the Ethertype.";
      reference "IEEE 802.3 and IETF RFC 7042 in hexadecimal representation.";
    }
    leaf fDesc {
      type string;
      description "It contains the flow description for the Uplink or Downlink IP flow. It shall be present when the ethtype is IP.";
    }
    leaf fDir {
      type enumeration {
        enum DOWNLINK;
        enum UPLINK;
      }
      mandatory true;
      description "It indicates the packet filter direction.";
    }
    leaf sourceMacAddr {
      type string;
      mandatory true;
      description "It specifies the source MAC address formatted in the
        hexadecimal notation.";
      reference "clause 1.1 and clause 2.1 of IETF RFC 7042";
    }
    leaf-list vlanTags {
      type string;
      description "It specifies the Customer-VLAN and/or Service-VLAN tags
        containing the VID, PCP/DEI fields as defined in IEEE 802.1Q and
        IETF RFC 7042. The first/lower instance in the array stands for the
        Customer-VLAN tag and the second/higher instance in the array stands
        for the Service-VLAN tag.";
    }
    leaf srcMacAddrEnd {
      type string;
      description "It specifies the source MAC address end. If this attribute is present, the sourceMacAddr attribute specifies the source MAC address start. E.g. srcMacAddrEnd with value 00-10-A4-23-3E-FE and sourceMacAddr with value 00-10-A4-23-3E-02 means all MAC addresses from 00-10-A4-23-3E-02 up to and including 00-10-A4-23-3E-FE.";
    }
    leaf destMacAddrEnd {
      type string;
      description "It specifies the destination MAC address end. If this attribute is present, the destMacAddr attribute specifies the destination MAC address start.";
    }
  }

  grouping FlowInformation {
    description "It specifies the flow information of a PCC rule.";
    leaf flowDescription {
      type string;
      mandatory true;
      description "It defines a packet filter for an IP flow.";
    }
    uses EthFlowDescription;
    leaf packFiltId {
      type string;
      mandatory true;
      description "It is the identifier of the packet filter.";
    }
    leaf packetFilterUsage {
      type boolean;
      default false;
      description "It indicates if the packet shall be sent to the UE.";
    }
    leaf tosTrafficClass {
      type string;
      mandatory true;
      description "It contains the Ipv4 Type-of-Service and mask field or the Ipv6 Traffic-Class field and mask field.";
    }
    leaf spi {
      type string;
      mandatory true;
      description "It is the security parameter index of the IPSec packet.";
      reference "IETF RFC 4301";
    }
    leaf flowLabel {
      type string;
      description "It specifies the Ipv6 flow label header field.";
    }
    leaf flowDirection {
      type enumeration {
        enum DOWNLINK;
        enum UPLINK;
        enum BIDIRECTIONAL;
        enum UNSPECIFIED;
      }
      mandatory true;
      description "It indicates the direction/directions that a filter is applicable.";
    }
  }

  grouping PccRule {
    description "It specifies the PCC rule, see TS 29.512";
    leaf pccRuleId {
      type string;
      mandatory true;
      description "It identifies the PCC rule.";
    }
    container flowInfoList {
      description "It is a list of IP flow packet filter information.";
      list flowInfo {
        description "The list of IP flow packet filter information.";
        key "packFiltId";
        uses FlowInformation;
      }
    }
    leaf applicationId {
      type string;
      default false;
      description "A reference to the application detection filter configured
        at the UPF.";
    }
    leaf appDescriptor {
      type string;
      description "It is the ATSSS rule application descriptor.";
    }
    leaf contentVersion {
      type uint8;
      description "Indicates the content version of the PCC rule.";
    }
    leaf precedence {
      type uint8 {
        range 0..255;
      }
      description "It indicates the order in which this PCC rule is applied
        relative to other PCC rules within the same PDU session.";
    }
    leaf afSigProtocol {
      type enumeration {
        enum NO_INFORMATION;
        enum SIP;
      }
      description "Indicates the protocol used for signalling between the UE
        and the AF, the default value is NO_INFORMATION.";
    }
    leaf isAppRelocatable {
      type boolean;
      default false;
      description "It indicates the application relocation possibility, the
        default value is NO_INFORMATION.";
    }
    leaf isUeAddrPreserved {
      type boolean;
      default false;
      description "It Indicates whether UE IP address should be preserved.";
    }
    container qosData {
      description "It contains the QoS control policy data for a PCC rule.";
      list qosDataInfo {
        description "The list of QoS control policy data.";
        key "qosId";
        uses QosDataInformation;
      }
    }
    container altQosParams {
      description "It contains the QoS control policy data for the Alternative
        QoS parameter sets of the service data flow.";
      list qosDataInfo {
        description "The list of QoS control policy data.";
        key "qosId";
        uses QosDataInformation;
      }
    }
    container trafficControlData {
      description "It contains the traffic control policy data for a PCC rule.";
      list trafficControlDataInfo {
        description "The list of traffic control policy data.";
        key "tcId";
        uses TrafficControlDataInformation;
      }
    }
    uses ConditionData;
    container tscaiInputUl {
      description "It contains transports TSCAI input parameters for TSC traffic at the ingress interface of the DS-TT/UE (uplink flow direction).";
      uses TscaiInputContainer;

    }
    container tscaiInputDl {
      description "It contains transports TSCAI input parameters for TSC traffic at the ingress of the NW-TT (downlink flow direction).";
      uses TscaiInputContainer;
    }
     leaf easRedisIndRequired {
      type boolean;
      default false;
      description "Indicates whether the EAS rediscovery is required for the application.";
    }
     leaf tscaiTimeDom {
      type uint32;
      description "Indicates the (g)PTP domain that the (TSN)AF is located in.";
    }
     leaf capBatNotificationCapable {
      type boolean;
      default false;
      description "Indicates the capability for AF to adjust the burst sending time.";
    }
     leaf ueNotifEnabled {
      type boolean;
      default false;
      description "Indicates whether QoS flow parameter signalling to the UE is enabled (TRUE), when the SMF is notified by the NG-RAN of changes in the fulfilled QoS situation,";
    }
     leaf packFiltAllPrec {
      type uint32;
      description "Determines the order of TFT packet filter allocation for PCC rules.";
    }
    leaf nscSupportedFeats {
      type uint32;
      description "Indicates the Network Function Service Consumer features supported per service.";
    }
  }

  grouping PredefinedPccRuleSetGrp {
    description "Represents the PredefinedPccRuleSet IOC.";
    list PredefinedPccRules {
      description "The list of predefined PCC rules.";
      key "pccRuleId";
      uses PccRule;
    }
  }

  grouping PredefinedPccRuleSetSubtree {
    description "It specifies the PredefinedPccRuleSet IOC with inherited attributes.";
    list PredefinedPccRuleSet {
      description "Specifies the predefined PCC rules.";
      key "id";
      uses top3gpp:Top_Grp;
      container attributes {
        description "It contains the attributes defined specifically in the PredefinedPccRuleSet IOC.";
        uses PredefinedPccRuleSetGrp;
      }
    }
  }

  augment "/me3gpp:ManagedElement/smf3gpp:SMFFunction" {
    description "It specifies the containment relation of PredefinedPccRuleSet MOI with SMFFunction MOI.";
    uses PredefinedPccRuleSetSubtree;
  }

  augment "/me3gpp:ManagedElement/pcf3gpp:PCFFunction" {
    description "It specifies the containment relation of PredefinedPccRuleSet MOI with PCFFunction MOI.";
    uses PredefinedPccRuleSetSubtree;
  }
}
